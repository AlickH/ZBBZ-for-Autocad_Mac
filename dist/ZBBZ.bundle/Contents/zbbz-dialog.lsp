(defun zbbz-dialog-bool-to-tile (value)
  (if value "1" "0"))

(setq *zbbz-dialog-initializing* nil)
(setq *zbbz-dialog-settings* nil)

(defun zbbz-dialog-temp-config-path ()
  (zbbz-plugin-path "zbbz-config.tmp.lsp"))

(defun zbbz-dialog-save-temp-config (/ file_handle)
  (setq file_handle (open (zbbz-dialog-temp-config-path) "w"))
  (if file_handle
    (progn
      (write-line (vl-prin1-to-string *zbbz-dialog-settings*) file_handle)
      (close file_handle)
      T)
    nil))

(defun zbbz-dialog-load-temp-config (/ file_handle config_line config_value)
  (setq file_handle (open (zbbz-dialog-temp-config-path) "r"))
  (if file_handle
    (progn
      (setq config_line (read-line file_handle))
      (close file_handle)
      (if config_line
        (progn
          (setq config_value (read config_line))
          (if config_value
            (zbbz-state-normalize-settings config_value)
            nil))
        nil))
    nil))

(defun zbbz-dialog-delete-temp-config ()
  (if (findfile (zbbz-dialog-temp-config-path))
    (vl-file-delete (zbbz-dialog-temp-config-path))))

(defun zbbz-dialog-begin-session ()
  (setq *zbbz-dialog-settings* (zbbz-state-ensure))
  (zbbz-dialog-save-temp-config))

(defun zbbz-dialog-end-session ()
  (zbbz-dialog-delete-temp-config)
  (setq *zbbz-dialog-settings* nil))

(defun zbbz-dialog-get (key / pair)
  (zbbz-state-assoc-value key (if *zbbz-dialog-settings* *zbbz-dialog-settings* (zbbz-state-ensure))))

(defun zbbz-dialog-put (key value / pair)
  (if (zbbz-state-boolean-key-p key)
    (setq value (if (zbbz-state-truthy-p value) T nil)))
  (if (null *zbbz-dialog-settings*)
    (zbbz-dialog-begin-session))
  (setq pair (assoc key *zbbz-dialog-settings*))
  (if pair
    (setq *zbbz-dialog-settings* (subst (cons key value) pair *zbbz-dialog-settings*))
    (setq *zbbz-dialog-settings* (append *zbbz-dialog-settings* (list (cons key value)))))
  (zbbz-dialog-save-temp-config)
  *zbbz-dialog-settings*)

(defun zbbz-dialog-put-many (pairs / pair)
  (foreach pair pairs
    (zbbz-dialog-put (car pair) (cdr pair)))
  *zbbz-dialog-settings*)

(defun zbbz-dialog-commit-session (/ temp_settings)
  (setq temp_settings (zbbz-dialog-load-temp-config))
  (if temp_settings
    (setq *zbbz-dialog-settings* temp_settings))
  (if *zbbz-dialog-settings*
    (zbbz-state-put-many *zbbz-dialog-settings*)))

(defun zbbz-dialog-lispsys ()
  (getvar "LISPSYS"))

(defun zbbz-dialog-unicode-supported-p ()
  (/= (zbbz-dialog-lispsys) 0))

(defun zbbz-dialog-language-source ()
  (strcat
    (if (zbbz-dialog-system-language-first) (strcase (zbbz-dialog-system-language-first)) "")
    "|"
    (if (getenv "LANG") (strcase (getenv "LANG")) "")
    "|"
    (if (getenv "LC_ALL") (strcase (getenv "LC_ALL")) "")
    "|"
    (if (getenv "LC_MESSAGES") (strcase (getenv "LC_MESSAGES")) "")
    "|"
    (if (getenv "APPLELOCALE") (strcase (getenv "APPLELOCALE")) "")))

(defun zbbz-dialog-language-setting ()
  (zbbz-dialog-get 'dialog_language))

(defun zbbz-dialog-preferences-dir ()
  (strcat (getenv "HOME") "/Library/Preferences"))

(defun zbbz-dialog-system-preference-plist-paths ()
  (list
    (strcat (zbbz-dialog-preferences-dir) "/.GlobalPreferences.plist")
    (strcat (zbbz-dialog-preferences-dir) "/.GlobalPreferences_m.plist")))

(defun zbbz-dialog-vl-registry-read-safe (reg_key val_name / result)
  (setq result (vl-catch-all-apply 'vl-registry-read (list reg_key val_name)))
  (if (vl-catch-all-error-p result)
    nil
    result))

(defun zbbz-dialog-first-quoted-string (text / index length start end)
  (setq index 1)
  (setq length (strlen text))
  (setq start nil)
  (setq end nil)
  (while (and (null start) (<= index length))
    (if (= (substr text index 1) "\"")
      (setq start (+ index 1)))
    (setq index (+ index 1)))
  (while (and start (null end) (<= index length))
    (if (= (substr text index 1) "\"")
      (setq end index))
    (setq index (+ index 1)))
  (if (and start end)
    (substr text start (- end start))))

(defun zbbz-dialog-language-first-from-value (value / text)
  (cond
    ((= (type value) 'STR) value)
    ((and (= (type value) 'LIST) (= (type (car value)) 'STR)) (car value))
    (T
      (setq text (vl-prin1-to-string value))
      (zbbz-dialog-first-quoted-string text))))

(defun zbbz-dialog-system-preference-keys (/ keys plist_path)
  (setq keys (list "Apple Global Domain" "NSGlobalDomain" ".GlobalPreferences"))
  (foreach plist_path (zbbz-dialog-system-preference-plist-paths)
    (setq keys
      (append keys
        (list
          plist_path
          (substr plist_path 1 (- (strlen plist_path) 6))))))
  keys)

(defun zbbz-dialog-system-preference-value (value_name / preference_key value)
  (setq value nil)
  (foreach preference_key (zbbz-dialog-system-preference-keys)
    (if (null value)
      (setq value (zbbz-dialog-vl-registry-read-safe preference_key value_name))))
  value)

(defun zbbz-dialog-system-language-first (/ language)
  (setq language
    (zbbz-dialog-language-first-from-value
      (zbbz-dialog-system-preference-value "AppleLanguages")))
  (if language
    language
    (zbbz-dialog-language-first-from-value
      (zbbz-dialog-system-preference-value "AppleLocale"))))

(defun zbbz-dialog-language-code-from-tag (language_tag / source)
  (setq source (strcase language_tag))
  (cond
    ((or (wcmatch source "ZH-*") (wcmatch source "ZH_*") (= source "ZH")) "zh")
    ((or (wcmatch source "FR-*") (wcmatch source "FR_*") (= source "FR")) "fr")
    ((or (wcmatch source "DE-*") (wcmatch source "DE_*") (= source "DE")) "de")
    ((or (wcmatch source "IT-*") (wcmatch source "IT_*") (= source "IT")) "it")
    ((or (wcmatch source "JA-*") (wcmatch source "JA_*") (= source "JA")) "ja")
    ((or (wcmatch source "KO-*") (wcmatch source "KO_*") (= source "KO")) "ko")
    ((or (wcmatch source "ES-*") (wcmatch source "ES_*") (= source "ES")) "es")
    (T "en")))

(defun zbbz-dialog-language-debug-lines ()
  (list
    (strcat "LISPSYS=" (if (zbbz-dialog-lispsys) (vl-prin1-to-string (zbbz-dialog-lispsys)) "nil"))
    (strcat "SYSTEM_LANGUAGE_FIRST=" (if (zbbz-dialog-system-language-first) (vl-prin1-to-string (zbbz-dialog-system-language-first)) "nil"))
    (strcat "LOCALE=" (if (getvar "LOCALE") (vl-prin1-to-string (getvar "LOCALE")) "nil"))
    (strcat "LANG=" (if (getenv "LANG") (vl-prin1-to-string (getenv "LANG")) "nil"))
    (strcat "LC_ALL=" (if (getenv "LC_ALL") (vl-prin1-to-string (getenv "LC_ALL")) "nil"))
    (strcat "LC_MESSAGES=" (if (getenv "LC_MESSAGES") (vl-prin1-to-string (getenv "LC_MESSAGES")) "nil"))
    (strcat "APPLELOCALE=" (if (getenv "APPLELOCALE") (vl-prin1-to-string (getenv "APPLELOCALE")) "nil"))
    (strcat "LANGUAGE_SOURCE=" (vl-prin1-to-string (zbbz-dialog-language-source)))
    (strcat "LANGUAGE_KEY=" (vl-prin1-to-string (zbbz-dialog-language-key)))))

(defun zbbz-dialog-print-language-debug ()
  (foreach line (zbbz-dialog-language-debug-lines)
    (prompt (strcat "\n" line))))

(defun zbbz-dialog-auto-language-key ()
  (zbbz-dialog-language-code-from-tag
    (if (zbbz-dialog-system-language-first)
      (zbbz-dialog-system-language-first)
      "en")))

(defun zbbz-dialog-language-key (/ setting)
  (setq setting (zbbz-dialog-language-setting))
  (if (member setting '("en" "zh" "fr" "de" "it" "ja" "ko" "es"))
    (setq setting setting)
    (setq setting (zbbz-dialog-auto-language-key)))
  setting)

(defun zbbz-dialog-follow-system-label (/ language_key)
  (setq language_key (zbbz-dialog-language-key))
  (cond
    ((= language_key "zh") "跟随系统语言")
    ((= language_key "fr") "Suivre la langue du systeme")
    ((= language_key "de") "Systemsprache folgen")
    ((= language_key "it") "Segui lingua di sistema")
    ((= language_key "ja") "システム言語に合わせる")
    ((= language_key "ko") "시스템 언어 따르기")
    ((= language_key "es") "Seguir idioma del sistema")
    (T "Follow System")))

(defun zbbz-dialog-language-options ()
  (list
    (cons "system" (zbbz-dialog-follow-system-label))
    (cons "en" "English")
    (cons "zh" "简体中文 (Chinese, Simplified)")
    (cons "fr" "français (French)")
    (cons "de" "Deutsch (German)")
    (cons "it" "italiano (Italian)")
    (cons "ja" "日本語 (Japanese)")
    (cons "ko" "한국어 (Korean)")
    (cons "es" "español (Spanish)")))

(defun zbbz-dialog-language-list-string (/ options list_string)
  (setq options (zbbz-dialog-language-options))
  (setq list_string "")
  (foreach option options
    (if (= list_string "")
      (setq list_string (cdr option))
      (setq list_string (strcat list_string "\\n" (cdr option)))))
  list_string)

(defun zbbz-dialog-language-index (/ options target_code index found_index)
  (setq options (zbbz-dialog-language-options))
  (setq target_code (zbbz-dialog-language-setting))
  (setq index 0)
  (setq found_index 0)
  (foreach option options
    (if (= (car option) target_code)
      (setq found_index index))
    (setq index (+ index 1)))
  (itoa found_index))

(defun zbbz-dialog-translation-pairs (/ language_key)
  (setq language_key (zbbz-dialog-language-key))
  (cond
    ((= language_key "zh")
      (list
        (cons "ZBBZ Coordinate Annotation Settings" "ZBBZ 坐标标注设置")
        (cons "Coordinate System" "坐标系统")
        (cons "Current Coordinate System" "当前坐标系")
        (cons "World Coordinate System" "世界坐标系")
        (cons "Custom Coordinate System" "自定义坐标系")
        (cons "Base N" "基准北坐标")
        (cons "Base E" "基准东坐标")
        (cons "Rotation" "旋转角")
        (cons "Known Base Point && Angle" "已知基点与角度")
        (cons "Known Two-Point Pick" "已知两点校准")
        (cons "Draw Coordinate Grid" "绘制坐标网格")
        (cons "Preview" "预览")
        (cons "Preview is descriptive only." "仅用于显示预览。")
        (cons "Behavior" "行为")
        (cons "Swap X/Y" "交换 X/Y")
        (cons "Group On" "创建组")
        (cons "Auto Orient" "自动定向")
        (cons "Prefix" "前缀")
        (cons "None" "无")
        (cons "Style" "样式")
        (cons "Annotation Layer" "标注图层")
        (cons "*CURRENT*\\n0" "*当前*\\n0")
        (cons "Arrow Style" "箭头样式")
        (cons "triangle\\nnone" "三角箭头\\n无")
        (cons "Arrow Size" "箭头大小")
        (cons "Text Style" "文字样式")
        (cons "Precision" "精度")
        (cons "Bearing" "方位角")
        (cons "Pick" "选择")
        (cons "Annotation Scale" "标注比例")
        (cons "Text Height" "文字高度")
        (cons "Background Mask" "背景遮罩")
        (cons "Dialog Language" "界面语言")
        (cons "Generate DAT File" "导出 DAT 文件")
        (cons "OK" "确定")
        (cons "Cancel" "取消")))
    ((= language_key "fr")
      (list
        (cons "ZBBZ Coordinate Annotation Settings" "Parametres d'annotation de coordonnees ZBBZ")
        (cons "Coordinate System" "Systeme de coordonnees")
        (cons "Current Coordinate System" "Systeme de coordonnees courant")
        (cons "World Coordinate System" "Systeme de coordonnees mondial")
        (cons "Custom Coordinate System" "Systeme de coordonnees personnalise")
        (cons "Base N" "Base N")
        (cons "Base E" "Base E")
        (cons "Rotation" "Rotation")
        (cons "Known Base Point && Angle" "Point de base et angle connus")
        (cons "Known Two-Point Pick" "Etalonnage a deux points")
        (cons "Draw Coordinate Grid" "Dessiner la grille de coordonnees")
        (cons "Preview" "Apercu")
        (cons "Preview is descriptive only." "L'apercu est purement descriptif.")
        (cons "Behavior" "Comportement")
        (cons "Swap X/Y" "Inverser X/Y")
        (cons "Group On" "Grouper")
        (cons "Auto Orient" "Orientation automatique")
        (cons "Prefix" "Prefixe")
        (cons "None" "Aucun")
        (cons "Style" "Style")
        (cons "Annotation Layer" "Calque d'annotation")
        (cons "*CURRENT*\\n0" "*ACTUEL*\\n0")
        (cons "Arrow Style" "Style de fleche")
        (cons "triangle\\nnone" "triangle\\naucun")
        (cons "Arrow Size" "Taille de la fleche")
        (cons "Text Style" "Style de texte")
        (cons "Precision" "Precision")
        (cons "Bearing" "Gisement")
        (cons "Pick" "Choisir")
        (cons "Annotation Scale" "Echelle d'annotation")
        (cons "Text Height" "Hauteur du texte")
        (cons "Background Mask" "Masque d'arriere-plan")
        (cons "Dialog Language" "Langue de l'interface")
        (cons "Generate DAT File" "Generer le fichier DAT")
        (cons "OK" "OK")
        (cons "Cancel" "Annuler")))
    ((= language_key "de")
      (list
        (cons "ZBBZ Coordinate Annotation Settings" "ZBBZ-Koordinatenbeschriftungseinstellungen")
        (cons "Coordinate System" "Koordinatensystem")
        (cons "Current Coordinate System" "Aktuelles Koordinatensystem")
        (cons "World Coordinate System" "Weltkoordinatensystem")
        (cons "Custom Coordinate System" "Benutzerdefiniertes Koordinatensystem")
        (cons "Base N" "Basis N")
        (cons "Base E" "Basis E")
        (cons "Rotation" "Drehung")
        (cons "Known Base Point && Angle" "Bekannter Basispunkt und Winkel")
        (cons "Known Two-Point Pick" "Bekannte Zweipunktkalibrierung")
        (cons "Draw Coordinate Grid" "Koordinatengitter zeichnen")
        (cons "Preview" "Vorschau")
        (cons "Preview is descriptive only." "Die Vorschau dient nur zur Anzeige.")
        (cons "Behavior" "Verhalten")
        (cons "Swap X/Y" "X/Y tauschen")
        (cons "Group On" "Gruppieren")
        (cons "Auto Orient" "Automatisch ausrichten")
        (cons "Prefix" "Prafix")
        (cons "None" "Keine")
        (cons "Style" "Stil")
        (cons "Annotation Layer" "Beschriftungsebene")
        (cons "*CURRENT*\\n0" "*AKTUELL*\\n0")
        (cons "Arrow Style" "Pfeilstil")
        (cons "triangle\\nnone" "Dreieck\\nkeine")
        (cons "Arrow Size" "Pfeilgroesse")
        (cons "Text Style" "Textstil")
        (cons "Precision" "Genauigkeit")
        (cons "Bearing" "Richtung")
        (cons "Pick" "Wahlen")
        (cons "Annotation Scale" "Beschriftungsmassstab")
        (cons "Text Height" "Texthoehe")
        (cons "Background Mask" "Hintergrundmaske")
        (cons "Dialog Language" "Dialogs Sprache")
        (cons "Generate DAT File" "DAT-Datei erzeugen")
        (cons "OK" "OK")
        (cons "Cancel" "Abbrechen")))
    ((= language_key "it")
      (list
        (cons "ZBBZ Coordinate Annotation Settings" "Impostazioni annotazione coordinate ZBBZ")
        (cons "Coordinate System" "Sistema di coordinate")
        (cons "Current Coordinate System" "Sistema di coordinate corrente")
        (cons "World Coordinate System" "Sistema di coordinate globale")
        (cons "Custom Coordinate System" "Sistema di coordinate personalizzato")
        (cons "Base N" "Base N")
        (cons "Base E" "Base E")
        (cons "Rotation" "Rotazione")
        (cons "Known Base Point && Angle" "Punto base e angolo noti")
        (cons "Known Two-Point Pick" "Calibrazione a due punti")
        (cons "Draw Coordinate Grid" "Disegna griglia coordinate")
        (cons "Preview" "Anteprima")
        (cons "Preview is descriptive only." "L'anteprima e solo descrittiva.")
        (cons "Behavior" "Comportamento")
        (cons "Swap X/Y" "Scambia X/Y")
        (cons "Group On" "Raggruppa")
        (cons "Auto Orient" "Orientamento automatico")
        (cons "Prefix" "Prefisso")
        (cons "None" "Nessuno")
        (cons "Style" "Stile")
        (cons "Annotation Layer" "Layer annotazione")
        (cons "*CURRENT*\\n0" "*CORRENTE*\\n0")
        (cons "Arrow Style" "Stile freccia")
        (cons "triangle\\nnone" "triangolo\\nnessuno")
        (cons "Arrow Size" "Dimensione freccia")
        (cons "Text Style" "Stile testo")
        (cons "Precision" "Precisione")
        (cons "Bearing" "Direzione")
        (cons "Pick" "Scegli")
        (cons "Annotation Scale" "Scala annotazione")
        (cons "Text Height" "Altezza testo")
        (cons "Background Mask" "Maschera sfondo")
        (cons "Dialog Language" "Lingua finestra")
        (cons "Generate DAT File" "Genera file DAT")
        (cons "OK" "OK")
        (cons "Cancel" "Annulla")))
    ((= language_key "ja")
      (list
        (cons "ZBBZ Coordinate Annotation Settings" "ZBBZ 座標注記設定")
        (cons "Coordinate System" "座標系")
        (cons "Current Coordinate System" "現在の座標系")
        (cons "World Coordinate System" "ワールド座標系")
        (cons "Custom Coordinate System" "カスタム座標系")
        (cons "Base N" "基準 N")
        (cons "Base E" "基準 E")
        (cons "Rotation" "回転角")
        (cons "Known Base Point && Angle" "既知の基点と角度")
        (cons "Known Two-Point Pick" "既知の 2 点校正")
        (cons "Draw Coordinate Grid" "座標グリッドを作図")
        (cons "Preview" "プレビュー")
        (cons "Preview is descriptive only." "プレビューは表示用です。")
        (cons "Behavior" "動作")
        (cons "Swap X/Y" "X/Y を入れ替え")
        (cons "Group On" "グループ化")
        (cons "Auto Orient" "自動方向調整")
        (cons "Prefix" "接頭辞")
        (cons "None" "なし")
        (cons "Style" "スタイル")
        (cons "Annotation Layer" "注記レイヤー")
        (cons "*CURRENT*\\n0" "*現在*\\n0")
        (cons "Arrow Style" "矢印スタイル")
        (cons "triangle\\nnone" "三角\\nなし")
        (cons "Arrow Size" "矢印サイズ")
        (cons "Text Style" "文字スタイル")
        (cons "Precision" "精度")
        (cons "Bearing" "方位角")
        (cons "Pick" "選択")
        (cons "Annotation Scale" "注記尺度")
        (cons "Text Height" "文字高さ")
        (cons "Background Mask" "背景マスク")
        (cons "Dialog Language" "ダイアログ言語")
        (cons "Generate DAT File" "DAT ファイルを生成")
        (cons "OK" "OK")
        (cons "Cancel" "キャンセル")))
    ((= language_key "ko")
      (list
        (cons "ZBBZ Coordinate Annotation Settings" "ZBBZ 좌표 주석 설정")
        (cons "Coordinate System" "좌표계")
        (cons "Current Coordinate System" "현재 좌표계")
        (cons "World Coordinate System" "월드 좌표계")
        (cons "Custom Coordinate System" "사용자 좌표계")
        (cons "Base N" "기준 N")
        (cons "Base E" "기준 E")
        (cons "Rotation" "회전각")
        (cons "Known Base Point && Angle" "기준점 및 각도 지정")
        (cons "Known Two-Point Pick" "2점 기준 보정")
        (cons "Draw Coordinate Grid" "좌표 그리드 작성")
        (cons "Preview" "미리보기")
        (cons "Preview is descriptive only." "미리보기는 설명용입니다.")
        (cons "Behavior" "동작")
        (cons "Swap X/Y" "X/Y 바꾸기")
        (cons "Group On" "그룹화")
        (cons "Auto Orient" "자동 방향")
        (cons "Prefix" "접두어")
        (cons "None" "없음")
        (cons "Style" "스타일")
        (cons "Annotation Layer" "주석 레이어")
        (cons "*CURRENT*\\n0" "*현재*\\n0")
        (cons "Arrow Style" "화살표 스타일")
        (cons "triangle\\nnone" "삼각형\\n없음")
        (cons "Arrow Size" "화살표 크기")
        (cons "Text Style" "문자 스타일")
        (cons "Precision" "정밀도")
        (cons "Bearing" "방위각")
        (cons "Pick" "선택")
        (cons "Annotation Scale" "주석 축척")
        (cons "Text Height" "문자 높이")
        (cons "Background Mask" "배경 마스크")
        (cons "Dialog Language" "대화상자 언어")
        (cons "Generate DAT File" "DAT 파일 생성")
        (cons "OK" "확인")
        (cons "Cancel" "취소")))
    ((= language_key "es")
      (list
        (cons "ZBBZ Coordinate Annotation Settings" "Configuracion de anotacion de coordenadas ZBBZ")
        (cons "Coordinate System" "Sistema de coordenadas")
        (cons "Current Coordinate System" "Sistema de coordenadas actual")
        (cons "World Coordinate System" "Sistema de coordenadas global")
        (cons "Custom Coordinate System" "Sistema de coordenadas personalizado")
        (cons "Base N" "Base N")
        (cons "Base E" "Base E")
        (cons "Rotation" "Rotacion")
        (cons "Known Base Point && Angle" "Punto base y angulo conocidos")
        (cons "Known Two-Point Pick" "Calibracion de dos puntos")
        (cons "Draw Coordinate Grid" "Dibujar cuadricula de coordenadas")
        (cons "Preview" "Vista previa")
        (cons "Preview is descriptive only." "La vista previa es solo descriptiva.")
        (cons "Behavior" "Comportamiento")
        (cons "Swap X/Y" "Intercambiar X/Y")
        (cons "Group On" "Agrupar")
        (cons "Auto Orient" "Orientacion automatica")
        (cons "Prefix" "Prefijo")
        (cons "None" "Ninguno")
        (cons "Style" "Estilo")
        (cons "Annotation Layer" "Capa de anotacion")
        (cons "*CURRENT*\\n0" "*ACTUAL*\\n0")
        (cons "Arrow Style" "Estilo de flecha")
        (cons "triangle\\nnone" "triangulo\\nninguno")
        (cons "Arrow Size" "Tamano de flecha")
        (cons "Text Style" "Estilo de texto")
        (cons "Precision" "Precision")
        (cons "Bearing" "Rumbo")
        (cons "Pick" "Seleccionar")
        (cons "Annotation Scale" "Escala de anotacion")
        (cons "Text Height" "Altura de texto")
        (cons "Background Mask" "Mascara de fondo")
        (cons "Dialog Language" "Idioma del panel")
        (cons "Generate DAT File" "Generar archivo DAT")
        (cons "OK" "Aceptar")
        (cons "Cancel" "Cancelar")))
    (T nil)))

(defun zbbz-dialog-sorted-translation-pairs ()
  (vl-sort
    (zbbz-dialog-translation-pairs)
    '(lambda (left right)
       (> (strlen (car left)) (strlen (car right))))))

(defun zbbz-dialog-localize-line (line)
  (foreach pair (zbbz-dialog-sorted-translation-pairs)
    (setq line (vl-string-subst (cdr pair) (car pair) line)))
  line)

(defun zbbz-dialog-runtime-dcl-path ()
  (zbbz-plugin-path "zbbz-runtime.dcl"))

(defun zbbz-dialog-precision-index ()
  (cond
    ((= (zbbz-dialog-get 'precision) 2) "1")
    ((= (zbbz-dialog-get 'precision) 1) "2")
    ((= (zbbz-dialog-get 'precision) 0) "3")
    ((= (zbbz-dialog-get 'precision) 4) "4")
    (T "0")))

(defun zbbz-dialog-coord-mode-key ()
  (cond
    ((eq (zbbz-dialog-get 'coord_mode) 'world) "coord_world")
    ((eq (zbbz-dialog-get 'coord_mode) 'custom) "coord_custom")
    (T "coord_current")))

(defun zbbz-dialog-prefix-mode-key ()
  (cond
    ((eq (zbbz-dialog-get 'prefix_mode) 'ab) "prefix_ab")
    ((eq (zbbz-dialog-get 'prefix_mode) 'ne) "prefix_ne")
    ((eq (zbbz-dialog-get 'prefix_mode) 'none) "prefix_none")
    (T "prefix_xy")))

(defun zbbz-dialog-runtime-line (line / dim_layer text_style runtime_line)
  (cond
    ((equal line "      : radio_column { key = \"coord_mode\"; value = \"coord_current\";")
      (setq runtime_line (strcat "      : radio_column { key = \"coord_mode\"; value = \"" (zbbz-dialog-coord-mode-key) "\";")))
    ((equal line "        : radio_button { key = \"coord_current\"; label = \"Current Coordinate System\"; value = \"1\"; }")
      (setq runtime_line (strcat "        : radio_button { key = \"coord_current\"; label = \"Current Coordinate System\"; value = \"" (if (eq (zbbz-dialog-get 'coord_mode) 'current) "1" "0") "\"; }")))
    ((equal line "        : radio_button { key = \"coord_world\"; label = \"World Coordinate System\"; value = \"0\"; }")
      (setq runtime_line (strcat "        : radio_button { key = \"coord_world\"; label = \"World Coordinate System\"; value = \"" (if (eq (zbbz-dialog-get 'coord_mode) 'world) "1" "0") "\"; }")))
    ((equal line "        : radio_button { key = \"coord_custom\"; label = \"Custom Coordinate System\"; value = \"0\"; }")
      (setq runtime_line (strcat "        : radio_button { key = \"coord_custom\"; label = \"Custom Coordinate System\"; value = \"" (if (eq (zbbz-dialog-get 'coord_mode) 'custom) "1" "0") "\"; }")))
    ((equal line "      : edit_box { key = \"base_n\"; label = \"Base N\"; edit_width = 18; value = \"0.000000\"; }")
      (setq runtime_line (strcat "      : edit_box { key = \"base_n\"; label = \"Base N\"; edit_width = 18; value = \"" (zbbz-format-number (zbbz-dialog-get 'base_n) 6) "\"; }")))
    ((equal line "      : edit_box { key = \"base_e\"; label = \"Base E\"; edit_width = 18; value = \"0.000000\"; }")
      (setq runtime_line (strcat "      : edit_box { key = \"base_e\"; label = \"Base E\"; edit_width = 18; value = \"" (zbbz-format-number (zbbz-dialog-get 'base_e) 6) "\"; }")))
    ((equal line "      : edit_box { key = \"rotation\"; label = \"Rotation\"; edit_width = 18; value = \"0.000000\"; }")
      (setq runtime_line (strcat "      : edit_box { key = \"rotation\"; label = \"Rotation\"; edit_width = 18; value = \"" (zbbz-format-number (zbbz-dialog-get 'rotation) 6) "\"; }")))
    ((equal line "        : toggle { key = \"swap_xy\"; label = \"Swap X/Y\"; value = \"0\"; }")
      (setq runtime_line (strcat "        : toggle { key = \"swap_xy\"; label = \"Swap X/Y\"; value = \"" (zbbz-dialog-bool-to-tile (zbbz-dialog-get 'swap_xy)) "\"; }")))
    ((equal line "        : toggle { key = \"group_on\"; label = \"Group On\"; value = \"0\"; }")
      (setq runtime_line (strcat "        : toggle { key = \"group_on\"; label = \"Group On\"; value = \"" (zbbz-dialog-bool-to-tile (zbbz-dialog-get 'group_on)) "\"; }")))
    ((equal line "        : toggle { key = \"auto_orient\"; label = \"Auto Orient\"; value = \"0\"; }")
      (setq runtime_line (strcat "        : toggle { key = \"auto_orient\"; label = \"Auto Orient\"; value = \"" (zbbz-dialog-bool-to-tile (zbbz-dialog-get 'auto_orient)) "\"; }")))
    ((equal line "        : radio_row { key = \"prefix_mode\"; value = \"prefix_xy\";")
      (setq runtime_line (strcat "        : radio_row { key = \"prefix_mode\"; value = \"" (zbbz-dialog-prefix-mode-key) "\";")))
    ((equal line "          : radio_button { key = \"prefix_xy\"; label = \"XY\"; value = \"1\"; }")
      (setq runtime_line (strcat "          : radio_button { key = \"prefix_xy\"; label = \"XY\"; value = \"" (if (eq (zbbz-dialog-get 'prefix_mode) 'xy) "1" "0") "\"; }")))
    ((equal line "          : radio_button { key = \"prefix_ab\"; label = \"AB\"; value = \"0\"; }")
      (setq runtime_line (strcat "          : radio_button { key = \"prefix_ab\"; label = \"AB\"; value = \"" (if (eq (zbbz-dialog-get 'prefix_mode) 'ab) "1" "0") "\"; }")))
    ((equal line "          : radio_button { key = \"prefix_ne\"; label = \"NE\"; value = \"0\"; }")
      (setq runtime_line (strcat "          : radio_button { key = \"prefix_ne\"; label = \"NE\"; value = \"" (if (eq (zbbz-dialog-get 'prefix_mode) 'ne) "1" "0") "\"; }")))
    ((equal line "          : radio_button { key = \"prefix_none\"; label = \"None\"; value = \"0\"; }")
      (setq runtime_line (strcat "          : radio_button { key = \"prefix_none\"; label = \"None\"; value = \"" (if (eq (zbbz-dialog-get 'prefix_mode) 'none) "1" "0") "\"; }")))
    ((equal line "      : popup_list { key = \"dim_layer\"; label = \"Annotation Layer\"; list = \"*CURRENT*\\n0\"; value = \"0\"; }")
      (progn
        (setq dim_layer (zbbz-dialog-get 'dim_layer))
        (setq runtime_line (strcat "      : popup_list { key = \"dim_layer\"; label = \"Annotation Layer\"; list = \"*CURRENT*\\n0\"; value = \"" (if (equal dim_layer "0") "1" "0") "\"; }"))))
    ((equal line "      : popup_list { key = \"arrow_style\"; label = \"Arrow Style\"; list = \"triangle\\nnone\"; value = \"0\"; }")
      (setq runtime_line (strcat "      : popup_list { key = \"arrow_style\"; label = \"Arrow Style\"; list = \"triangle\\nnone\"; value = \"" (if (equal (zbbz-dialog-get 'arrow_style) "none") "1" "0") "\"; }")))
    ((equal line "      : edit_box { key = \"arrow_size\"; label = \"Arrow Size\"; edit_width = 12; value = \"2.500000\"; }")
      (setq runtime_line (strcat "      : edit_box { key = \"arrow_size\"; label = \"Arrow Size\"; edit_width = 12; value = \"" (zbbz-format-number (zbbz-dialog-get 'arrow_size) 6) "\"; }")))
    ((equal line "      : popup_list { key = \"text_style\"; label = \"Text Style\"; list = \"*CURRENT*\\nStandard\"; value = \"0\"; }")
      (progn
        (setq text_style (zbbz-dialog-get 'text_style))
        (setq runtime_line (strcat "      : popup_list { key = \"text_style\"; label = \"Text Style\"; list = \"*CURRENT*\\nStandard\"; value = \"" (if (equal text_style "Standard") "1" "0") "\"; }"))))
    ((equal line "      : popup_list { key = \"precision\"; label = \"Precision\"; list = \"0.000\\n0.00\\n0.0\\n0\\n0.0000\"; value = \"0\"; }")
      (setq runtime_line (strcat "      : popup_list { key = \"precision\"; label = \"Precision\"; list = \"0.000\\n0.00\\n0.0\\n0\\n0.0000\"; value = \"" (zbbz-dialog-precision-index) "\"; }")))
    ((equal line "      : popup_list { key = \"dialog_language\"; label = \"Dialog Language\"; list = \"Follow System\\nEnglish\\nChinese, Simplified\\nFrench\\nGerman\\nItalian\\nJapanese\\nKorean\\nSpanish\"; value = \"0\"; }")
      (setq runtime_line (strcat "      : popup_list { key = \"dialog_language\"; label = \"Dialog Language\"; list = \"" (zbbz-dialog-language-list-string) "\"; value = \"" (zbbz-dialog-language-index) "\"; }")))
    ((equal line "        : edit_box { key = \"bearing_angle\"; label = \"Bearing\"; edit_width = 12; value = \"0.000000\"; }")
      (setq runtime_line (strcat "        : edit_box { key = \"bearing_angle\"; label = \"Bearing\"; edit_width = 12; value = \"" (zbbz-format-number (zbbz-dialog-get 'bearing_angle) 6) "\"; }")))
    ((equal line "      : edit_box { key = \"dim_scale\"; label = \"Annotation Scale\"; edit_width = 12; value = \"1.000000\"; }")
      (setq runtime_line (strcat "      : edit_box { key = \"dim_scale\"; label = \"Annotation Scale\"; edit_width = 12; value = \"" (zbbz-format-number (zbbz-dialog-get 'dim_scale) 6) "\"; }")))
    ((equal line "      : edit_box { key = \"text_height\"; label = \"Text Height\"; edit_width = 12; value = \"2.500000\"; }")
      (setq runtime_line (strcat "      : edit_box { key = \"text_height\"; label = \"Text Height\"; edit_width = 12; value = \"" (zbbz-format-number (zbbz-dialog-get 'text_height) 6) "\"; }")))
    ((equal line "      : toggle { key = \"background_mask\"; label = \"Background Mask\"; value = \"0\"; }")
      (setq runtime_line (strcat "      : toggle { key = \"background_mask\"; label = \"Background Mask\"; value = \"" (zbbz-dialog-bool-to-tile (zbbz-dialog-get 'background_mask)) "\"; }")))
    (T
      (setq runtime_line line)))
  (zbbz-dialog-localize-line runtime_line))

(defun zbbz-dialog-write-runtime-dcl (/ source target line)
  (setq source (open (zbbz-plugin-path "zbbz.dcl") "r"))
  (setq target (open (zbbz-dialog-runtime-dcl-path) "w" "utf8-bom"))
  (if (and source target)
    (progn
      (while (setq line (read-line source))
        (write-line (zbbz-dialog-runtime-line line) target))
      (close source)
      (close target)
      (zbbz-dialog-runtime-dcl-path))
    (progn
      (if source (close source))
      (if target (close target))
      nil)))

(defun zbbz-dialog-sync-preview (/ lines)
  (setq lines
    (zbbz-format-output-lines
      0.0
      0.0
      (zbbz-dialog-get 'prefix_mode)
      (zbbz-dialog-get 'swap_xy)
      (zbbz-dialog-get 'precision)))
  (set_tile "preview_line_1" (car lines))
  (set_tile "preview_line_2" (cadr lines)))

(defun zbbz-dialog-update-custom-input-state (/ mode disabled_mode enabled_mode)
  (setq mode (zbbz-dialog-get 'coord_mode))
  (setq enabled_mode 0)
  (setq disabled_mode 1)
  (mode_tile "base_n" (if (eq mode 'custom) enabled_mode disabled_mode))
  (mode_tile "base_e" (if (eq mode 'custom) enabled_mode disabled_mode))
  (mode_tile "rotation" (if (eq mode 'custom) enabled_mode disabled_mode))
  (mode_tile "apply_base_angle" (if (eq mode 'custom) enabled_mode disabled_mode))
  (mode_tile "pick_two_points" enabled_mode))

(defun zbbz-dialog-populate ()
  (setq *zbbz-dialog-initializing* T)
  (set_tile "base_n" (zbbz-format-number (zbbz-dialog-get 'base_n) 6))
  (set_tile "base_e" (zbbz-format-number (zbbz-dialog-get 'base_e) 6))
  (set_tile "rotation" (zbbz-format-number (zbbz-dialog-get 'rotation) 6))
  (set_tile "arrow_size" (zbbz-format-number (zbbz-dialog-get 'arrow_size) 6))
  (set_tile "bearing_angle" (zbbz-format-number (zbbz-dialog-get 'bearing_angle) 6))
  (set_tile "dim_scale" (zbbz-format-number (zbbz-dialog-get 'dim_scale) 6))
  (set_tile "text_height" (zbbz-format-number (zbbz-dialog-get 'text_height) 6))
  (set_tile "background_mask" (zbbz-dialog-bool-to-tile (zbbz-dialog-get 'background_mask)))
  (set_tile "dialog_language" (zbbz-dialog-language-index))
  (zbbz-dialog-update-custom-input-state)
  (zbbz-dialog-sync-preview)
  (setq *zbbz-dialog-initializing* nil))

(defun zbbz-dialog-save-number-value (key raw_value / value)
  (setq value (distof raw_value 2))
  (if value
    (zbbz-dialog-put key value)))

(defun zbbz-dialog-save-toggle-value (key raw_value)
  (zbbz-dialog-put key (equal raw_value "1")))

(defun zbbz-dialog-save-dim-layer-value (raw_value)
  (zbbz-dialog-put 'dim_layer
    (if (= (atoi raw_value) 1) "0" "")))

(defun zbbz-dialog-save-arrow-style-value (raw_value)
  (zbbz-dialog-put 'arrow_style
    (if (= (atoi raw_value) 1) "none" "triangle")))

(defun zbbz-dialog-save-text-style-value (raw_value)
  (zbbz-dialog-put 'text_style
    (if (= (atoi raw_value) 1) "Standard" "")))

(defun zbbz-dialog-precision-value (raw_value / precision_index)
  (setq precision_index (atoi raw_value))
  (cond
    ((= precision_index 0) 3)
    ((= precision_index 1) 2)
    ((= precision_index 2) 1)
    ((= precision_index 3) 0)
    ((= precision_index 4) 4)
    (T 3)))

(defun zbbz-dialog-save-precision-value (raw_value)
  (zbbz-dialog-put 'precision (zbbz-dialog-precision-value raw_value)))

(defun zbbz-dialog-save-language-value (raw_value)
  (zbbz-dialog-put 'dialog_language
    (nth (atoi raw_value) '("system" "en" "zh" "fr" "de" "it" "ja" "ko" "es"))))

(defun zbbz-dialog-request-action (action_code)
  (setq *zbbz-dialog-action* action_code)
  (done_dialog 2))

(defun zbbz-dialog-handle-apply-base-angle (/ base_n base_e rotation)
  (setq base_n (distof (get_tile "base_n") 2))
  (setq base_e (distof (get_tile "base_e") 2))
  (setq rotation (distof (get_tile "rotation") 2))
  (if (and base_n base_e rotation)
    (progn
      (zbbz-dialog-put-many
        (list
          (cons 'coord_mode 'custom)
          (cons 'base_n base_n)
          (cons 'base_e base_e)
          (cons 'rotation rotation)))
      (zbbz-dialog-populate))))

(defun zbbz-dialog-bind-actions ()
  (action_tile "coord_current" "(if (not *zbbz-dialog-initializing*) (progn (zbbz-dialog-put 'coord_mode 'current) (zbbz-dialog-update-custom-input-state)))")
  (action_tile "coord_world" "(if (not *zbbz-dialog-initializing*) (progn (zbbz-dialog-put 'coord_mode 'world) (zbbz-dialog-update-custom-input-state)))")
  (action_tile "coord_custom" "(if (not *zbbz-dialog-initializing*) (progn (zbbz-dialog-put 'coord_mode 'custom) (zbbz-dialog-update-custom-input-state)))")
  (action_tile "base_n" "(if (not *zbbz-dialog-initializing*) (zbbz-dialog-save-number-value 'base_n $value))")
  (action_tile "base_e" "(if (not *zbbz-dialog-initializing*) (zbbz-dialog-save-number-value 'base_e $value))")
  (action_tile "rotation" "(if (not *zbbz-dialog-initializing*) (zbbz-dialog-save-number-value 'rotation $value))")
  (action_tile "swap_xy" "(if (not *zbbz-dialog-initializing*) (progn (zbbz-dialog-save-toggle-value 'swap_xy $value) (zbbz-dialog-sync-preview)))")
  (action_tile "group_on" "(if (not *zbbz-dialog-initializing*) (zbbz-dialog-save-toggle-value 'group_on $value))")
  (action_tile "auto_orient" "(if (not *zbbz-dialog-initializing*) (zbbz-dialog-save-toggle-value 'auto_orient $value))")
  (action_tile "background_mask" "(if (not *zbbz-dialog-initializing*) (zbbz-dialog-save-toggle-value 'background_mask $value))")
  (action_tile "prefix_xy" "(if (not *zbbz-dialog-initializing*) (progn (zbbz-dialog-put 'prefix_mode 'xy) (zbbz-dialog-sync-preview)))")
  (action_tile "prefix_ab" "(if (not *zbbz-dialog-initializing*) (progn (zbbz-dialog-put 'prefix_mode 'ab) (zbbz-dialog-sync-preview)))")
  (action_tile "prefix_ne" "(if (not *zbbz-dialog-initializing*) (progn (zbbz-dialog-put 'prefix_mode 'ne) (zbbz-dialog-sync-preview)))")
  (action_tile "prefix_none" "(if (not *zbbz-dialog-initializing*) (progn (zbbz-dialog-put 'prefix_mode 'none) (zbbz-dialog-sync-preview)))")
  (action_tile "dim_layer" "(if (not *zbbz-dialog-initializing*) (zbbz-dialog-save-dim-layer-value $value))")
  (action_tile "arrow_style" "(if (not *zbbz-dialog-initializing*) (zbbz-dialog-save-arrow-style-value $value))")
  (action_tile "arrow_size" "(if (not *zbbz-dialog-initializing*) (zbbz-dialog-save-number-value 'arrow_size $value))")
  (action_tile "text_style" "(if (not *zbbz-dialog-initializing*) (zbbz-dialog-save-text-style-value $value))")
  (action_tile "precision" "(if (not *zbbz-dialog-initializing*) (progn (zbbz-dialog-save-precision-value $value) (zbbz-dialog-sync-preview)))")
  (action_tile "dialog_language" "(if (not *zbbz-dialog-initializing*) (progn (zbbz-dialog-save-language-value $value) (zbbz-dialog-request-action 'refresh_language)))")
  (action_tile "bearing_angle" "(if (not *zbbz-dialog-initializing*) (zbbz-dialog-save-number-value 'bearing_angle $value))")
  (action_tile "dim_scale" "(if (not *zbbz-dialog-initializing*) (zbbz-dialog-save-number-value 'dim_scale $value))")
  (action_tile "text_height" "(if (not *zbbz-dialog-initializing*) (zbbz-dialog-save-number-value 'text_height $value))")
  (action_tile "apply_base_angle" "(zbbz-dialog-handle-apply-base-angle)")
  (action_tile "pick_two_points" "(zbbz-dialog-request-action 'pick_two_points)")
  (action_tile "draw_grid" "(zbbz-dialog-request-action 'draw_grid)")
  (action_tile "pick_bearing" "(zbbz-dialog-request-action 'pick_bearing)")
  (action_tile "export_dat" "(zbbz-dialog-request-action 'export_dat)")
  (action_tile "accept" "(setq *zbbz-dialog-action* 'accept) (done_dialog 1)")
  (action_tile "cancel" "(done_dialog 0)"))

(defun zbbz-dialog-run-once (/ runtime_dcl_path dialog_id result)
  (setq runtime_dcl_path (zbbz-dialog-write-runtime-dcl))
  (if (null runtime_dcl_path)
    (progn
      (prompt "\nUnable to write zbbz-runtime.dcl.")
      nil)
    (progn
      (setq dialog_id (load_dialog (zbbz-dialog-runtime-dcl-path)))
      (if (< dialog_id 0)
        (progn
          (prompt "\nUnable to load zbbz-runtime.dcl.")
          nil)
        (progn
          (if (not (new_dialog "SetDimZB" dialog_id))
            (progn
              (prompt "\nUnable to open SetDimZB dialog.")
              (setq result 0))
            (progn
              (setq *zbbz-dialog-action* 'accept)
              (zbbz-dialog-populate)
              (zbbz-dialog-bind-actions)
              (setq result (start_dialog))))
          (unload_dialog dialog_id)
          (list result *zbbz-dialog-action*))))))

(defun zbbz-dialog-open-loop (/ dialog_result dialog_code action_value bearing_angle calibration)
  (zbbz-dialog-begin-session)
  (setq action_value 'accept)
  (while action_value
    (if (null *zbbz-dialog-settings*)
      (zbbz-dialog-begin-session))
    (setq dialog_result (zbbz-dialog-run-once))
    (if (null dialog_result)
      (progn
        (zbbz-dialog-end-session)
        (setq action_value nil))
      (progn
        (setq dialog_code (car dialog_result))
        (setq action_value (cadr dialog_result))
        (cond
          ((= dialog_code 0)
            (zbbz-dialog-end-session)
            (setq action_value nil)
            nil)
          ((= dialog_code 1)
            (zbbz-dialog-commit-session)
            (zbbz-dialog-end-session)
            (setq action_value nil)
            T)
          ((eq action_value 'pick_bearing)
            (zbbz-dialog-commit-session)
            (setq bearing_angle (zbbz-pick-bearing-angle))
            (if bearing_angle
              (zbbz-state-put 'bearing_angle bearing_angle))
            (zbbz-dialog-end-session))
          ((eq action_value 'pick_two_points)
            (zbbz-dialog-commit-session)
            (zbbz-dialog-end-session)
            (setq calibration (zbbz-pick-two-point-calibration))
            (if calibration
              (zbbz-pick-apply-calibration calibration)))
          ((eq action_value 'refresh_language)
            T)
          ((eq action_value 'draw_grid)
            (zbbz-dialog-commit-session)
            (zbbz-dialog-end-session)
            (zbbz-grid-draw))
          ((eq action_value 'export_dat)
            (zbbz-dialog-commit-session)
            (zbbz-dialog-end-session)
            (zbbz-dat-export-session))
          (T
            (zbbz-dialog-end-session)
            (setq action_value nil)
            nil))))))
(setq *zbbz-dialog-action* 'accept)
